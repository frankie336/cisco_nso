module mpls-l3vpnv4-pr {

  namespace "http://example.com/mpls-l3vpnv4-pr";
  prefix mpls-l3vpnv4-pr;

  import ietf-inet-types {
    prefix inet;
  }
  
  //External modules are imported by this declaration.
  //Cisco NSO looks for external modules from local directory: ~nso-5.5/src/ncs/yang
  //Many IETF modules are available here : http://www.netconfcentral.org/modulelist
  //Ciso modules are avaiable here: https://github.com/YangModels/yang
  //Modules must be saved locally with the .yang extension
  import ietf-routing-types {
    prefix rt-types;
   
  }


  import tailf-common {
    prefix tailf;
  }
  import tailf-ncs {
    prefix ncs;
  }

  description
    "Bla bla...";

  revision 2016-01-01 {
    description
      "Initial revision.";
  }

 

  list mpls-l3vpnv4-pr {
    description "This is an RFS skeleton service";

    key name;
    leaf name {
      tailf:info "Unique service id";
      tailf:cli-allow-range;
      type string;
    }

    uses ncs:service-data;
    ncs:servicepoint mpls-l3vpnv4-pr-servicepoint;

    // may replace this with other ways of refering to the devices.
    leaf-list device {
      type leafref {
        path "/ncs:devices/ncs:device/ncs:name";
      }
    }
    

    //typedefs here
    //This section defines local structures that can be referenced by other leafs
    //and enforced. For example, here I am enforcing vlan numbering to range from 
    //100 - 4096
    typedef vlan-extended {
     type uint32 {
      range "100 .. 4096";
     }
     description "Extended vlan numbering";
    }
    
    //vrf name
    leaf vrf-name {
      tailf:info "vrf name";
      mandatory true;
      type string; 
    }
    
    
    leaf rd {
      tailf:info "Makes overlapping addresses unique";
      mandatory true;
      type rt-types:route-distinguisher;
      

    }
    leaf export {
      tailf:info "Export routes";
      mandatory true;
      type rt-types:route-target;
      

    }
    leaf import {
      tailf:info "Import routes";
      mandatory true;
      type rt-types:route-target;
     
    }

    leaf wan-interface-number {
      tailf:info "CE facing interface";
      mandatory true;
      type string;

    }
    
    leaf vlan{
      tailf:info "Sets the vlan number of the wan sub interface";
      mandatory true;
      type vlan-extended;    
      
    }

    leaf static_route_ip {
      type string;
      default "169.254.0.0";
    }

    leaf wan-ip-address {
      tailf:info "PE interface IP address";
      mandatory true;
      type inet:ipv4-address;

    }

    leaf ce-ip-address {
      tailf:info "Valid IP";
      mandatory true;
      type inet:ipv4-address;
    } 
    leaf bgp-password {
      tailf:info "BGP MD5 Password";
      mandatory true;
      type string;
    
  
    
    }
  }
}
