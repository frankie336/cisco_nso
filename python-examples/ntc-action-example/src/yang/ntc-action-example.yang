module ntc-action-example {

  namespace "http://networktocode.com/ntc-action-example";
  prefix ntc-action-example;

  import tailf-common {
    prefix tailf;
  }
  import tailf-ncs {
    prefix ncs;
  }

  description
    "An action example";

  revision 2019-09-12 {
    description
      "Giving some details for an action example.";
  }

  container action {
    tailf:action draw {
      tailf:actionpoint ntc-action-example-action;
      input {
        leaf confirm {
          type string;
        }
      }
      output {
        leaf result {
          type uint16;
        }
      }
    }
  }
}
